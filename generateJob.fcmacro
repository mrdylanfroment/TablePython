import sys
import os

# -----------------------------
# Add project folder to sys.path
# -----------------------------
project_path = "/home/dylan/temp2/TablePython"  # adjust to your repo path
if project_path not in sys.path:
    sys.path.append(project_path)

# -----------------------------
# Import project classes
# -----------------------------
from loader import Loader
from workshop import Job, Product, Component
from math import radians
# -----------------------------
# FreeCAD imports
# -----------------------------
import FreeCAD as App
import FreeCADGui as Gui
import Sketcher
import Part
from FreeCAD import Vector, Rotation

# -----------------------------
# Load YAML job
# -----------------------------
loader = Loader()
job = loader.load(os.path.join(project_path, "yaml/table.yaml"))

# -----------------------------
# Get or create FreeCAD document
# -----------------------------
doc = App.ActiveDocument
if not doc:
    doc = App.newDocument("TableJob")

# -----------------------------
# Function to create rectangle sketch and pad
# -----------------------------
def create_rectangle_pad(body, comp):
    """
    Create a centered rectangle sketch and symmetric pad in a PartDesign body.
    comp: component object with dimensions, position, rotation
    """
    # Create a sketch in the body
    sketch = doc.addObject('Sketcher::SketchObject', f"{comp.name}_sketch")
    body.addObject(sketch)
    sketch.MapMode = 'FlatFace'

    # Dimensions
    w = comp.dimensions['width']
    d = comp.dimensions['depth']
    h = comp.dimensions['height']

    # Rectangle corners, centered on origin
    x0 = -w/2
    y0 = -d/2
    sketch.addGeometry([
        Part.LineSegment(Vector(x0, y0, 0), Vector(x0 + w, y0, 0)),
        Part.LineSegment(Vector(x0 + w, y0, 0), Vector(x0 + w, y0 + d, 0)),
        Part.LineSegment(Vector(x0 + w, y0 + d, 0), Vector(x0, y0 + d, 0)),
        Part.LineSegment(Vector(x0, y0 + d, 0), Vector(x0, y0, 0))
    ], False)

    # Coincident constraints
    sketch.addConstraint(Sketcher.Constraint('Coincident', 0, 2, 1, 1))
    sketch.addConstraint(Sketcher.Constraint('Coincident', 1, 2, 2, 1))
    sketch.addConstraint(Sketcher.Constraint('Coincident', 2, 2, 3, 1))
    sketch.addConstraint(Sketcher.Constraint('Coincident', 3, 2, 0, 1))

    # Horizontal & vertical constraints
    sketch.addConstraint(Sketcher.Constraint('Horizontal', 0))
    sketch.addConstraint(Sketcher.Constraint('Vertical', 1))
    sketch.addConstraint(Sketcher.Constraint('Horizontal', 2))
    sketch.addConstraint(Sketcher.Constraint('Vertical', 3))

    # Set distances (width & depth)
    sketch.addConstraint(Sketcher.Constraint('Distance', 0, w))
    sketch.addConstraint(Sketcher.Constraint('Distance', 1, d))

    # Center rectangle on origin
    sketch.addConstraint(Sketcher.Constraint('DistanceX', 0, 1, x0))
    sketch.addConstraint(Sketcher.Constraint('DistanceY', 0, 1, y0))

    doc.recompute()

    # Create symmetric pad
    pad = doc.addObject("PartDesign::Pad", f"{comp.name}_pad")
    body.addObject(pad)
    pad.Profile = sketch
    pad.Length = h
    pad.Midplane = True  # symmetric padding

    doc.recompute()


# -----------------------------
# Generate components from job
# -----------------------------
for product_name, product in job.products.items():
    for comp_name, comp in product.components.items():
        # Create a body for this component
        body = doc.addObject('PartDesign::Body', comp_name)

        # Set placement (position + rotation)
        body.Placement.Base = Vector(
            comp.position['x'],
            comp.position['y'],
            comp.position['z']
        )


        body.Placement.Rotation = Rotation(
            radians(comp.rotation['x']),
            radians(comp.rotation['y']),
            radians(comp.rotation['z'])
        )

        # Create rectangle sketch and symmetric pad
        create_rectangle_pad(body, comp)

# -----------------------------
# Fit view
# -----------------------------
Gui.activeDocument().activeView().viewIsometric()
Gui.activeDocument().activeView().fitAll()

print("Job generated successfully!")
